S1AP-PDU-Descriptions  { itu-t (0) }

DEFINITIONS AUTOMATIC TAGS ::= 

BEGIN

IMPORTS
Criticality,
ProcedureCode
FROM S1AP-CommonDataTypes;

E-RABDataForwardingItem ::= SEQUENCE {
    e-RAB-IDE    RAB-ID
}

END
